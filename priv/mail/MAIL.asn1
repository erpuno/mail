MAIL DEFINITIONS IMPLICIT TAGS ::= BEGIN

    Adr ::= SEQUENCE { src OCTET STRING, dst CHOICE { muc [0] OCTET STRING, p2p [1] OCTET STRING } }
    Ack ::= SEQUENCE { lex OCTET STRING }
    Auth ::= SEQUENCE { tok OCTET STRING }
    Cut ::= SEQUENCE { id  OCTET STRING }
    Message ::= SEQUENCE { key OCTET STRING, adr Adr, tag OCTET STRING, bin OCTET STRING }
    MAILMessage ::= CHOICE { ack [0] Ack, n2o [1] Auth, cut [4] Cut, pub [3] Message }

END
